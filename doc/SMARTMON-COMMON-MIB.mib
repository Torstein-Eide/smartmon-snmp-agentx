SMARTMON-COMMON-MIB DEFINITIONS ::= BEGIN

IMPORTS
    MODULE-IDENTITY, OBJECT-TYPE, NOTIFICATION-TYPE,
    Unsigned32
        FROM SNMPv2-SMI
    DisplayString, DateAndTime
        FROM SNMPv2-TC
    PhysicalIndexOrZero
        FROM ENTITY-MIB
    MODULE-COMPLIANCE, OBJECT-GROUP, NOTIFICATION-GROUP
        FROM SNMPv2-CONF
    SmartmonDeviceType, SmartmonPollResult, SmartmonDevicePowerState,
    smartmonRoot
        FROM SMARTMON-TC-MIB;

smartmonCommonMIB MODULE-IDENTITY
    LAST-UPDATED "202606160000Z"
    ORGANIZATION "Unassigned"
    CONTACT-INFO
        "This is a draft MIB for smartmontools smartctl output.

         TODO: Replace the placeholder enterprise OID before publication."
    DESCRIPTION
        "The SMARTMON-COMMON-MIB defines the central device inventory
         shared by all SMARTMON protocol MIBs (NVMe, SATA, SAS).

         Every monitored device appears as one row in smartmonDeviceMetadataTable
         (and the corresponding smartmonDeviceStatusTable row),
         identified by a local smartmonDeviceIndex.  All protocol-specific
         tables use smartmonDeviceIndex as their first index component,
         so a manager can join any protocol table to this table on that
         index to obtain device identity and poll-status context.

         The scalar smartmonDeviceTableRowCount reflects the current number
         of rows in smartmonDeviceMetadataTable, and smartmonDeviceTableLastChange
         records when the table last changed.  A smartmonDeviceDiscovered
         notification is emitted whenever a new row is added, allowing
         managers to detect hot-plug or auto-discovered devices without
         polling the table continuously.

         This MIB requires SMARTMON-TC-MIB."
    REVISION "202606210000Z"
    DESCRIPTION
        "Split smartmonDeviceTable into smartmonDeviceMetadataTable
         (static identity columns: Name, Path, Type, PhysicalIndex, Uris,
         ModelFamily, ModelName, SerialNumber, FirmwareVersion, Wwn) and
         smartmonDeviceStatusTable (per-poll columns: LastPollTime,
         LastPollResult, LastPollExitStatus, PowerState), sharing the same
         smartmonDeviceIndex row set.  Also added smartmonDevicePowerState
         (was added to the old smartmonDeviceTable in the previous
         revision; now lives in smartmonDeviceStatusTable).  This is a
         breaking renumbering: smartmonDeviceTable, smartmonDeviceEntry,
         and SmartmonDeviceEntry no longer exist."
    REVISION "202606160000Z"
    DESCRIPTION
        "Add smartmonDeviceUdevTable, a generic name/value table of udevadm
         properties per device, and smartmonDeviceUdevTableLastChange.
         Populated only in collect mode (udevadm needs a live device node).
         smartmonDeviceWwn may now be populated for NVMe devices, sourced
         from udevadm's ID_WWN property when collect mode is active."
    REVISION "202605270000Z"
    DESCRIPTION
        "Add smartmonDeviceModelFamily, smartmonDeviceModelName,
         smartmonDeviceSerialNumber, smartmonDeviceFirmwareVersion,
         smartmonDeviceWwn columns to smartmonDeviceTable (cols 10-14).
         Model, serial, firmware, and WWN moved here from per-protocol
         tables (NVMe controller, SATA info, SAS info).
         smartmonDeviceIndex is now derived from a 32-bit FNV-1a hash of
         serial_number|model_name, making it likely to be consistent across
         agent restarts; managers must not treat it as a reliable persistent
         identifier."
    REVISION "202605200000Z"
    DESCRIPTION
        "Add smartmonDeviceCountNvme, smartmonDeviceCountAta,
         smartmonDeviceCountSas scalars; add smartmonDeviceUris
         column to smartmonDeviceTable."
    REVISION "202605180000Z"
    DESCRIPTION "Initial draft."
    ::= { smartmonRoot 2 }

-- --------------------------------------------------------------------------
-- Top-level structure
-- --------------------------------------------------------------------------

smartmonCommonObjects       OBJECT IDENTIFIER ::= { smartmonCommonMIB 1 }
smartmonCommonConformance   OBJECT IDENTIFIER ::= { smartmonCommonMIB 2 }
smartmonCommonNotifications OBJECT IDENTIFIER ::= { smartmonCommonMIB 3 }
smartmonCommonCompliances   OBJECT IDENTIFIER ::= { smartmonCommonConformance 1 }
smartmonCommonGroups        OBJECT IDENTIFIER ::= { smartmonCommonConformance 2 }

-- --------------------------------------------------------------------------
-- Table metadata scalars
-- --------------------------------------------------------------------------

smartmonDeviceTableRowCount OBJECT-TYPE
    SYNTAX      Unsigned32
    MAX-ACCESS  read-only
    STATUS      current
    DESCRIPTION
        "Total number of devices currently present in smartmonDeviceMetadataTable.
         This value increases when a new device is discovered and decreases
         when a device is removed from monitoring.  Managers MAY poll this
         object to detect table changes without walking the full table."
    ::= { smartmonCommonObjects 1 }

smartmonDeviceTableLastChange OBJECT-TYPE
    SYNTAX      DateAndTime
    MAX-ACCESS  read-only
    STATUS      current
    DESCRIPTION
        "Timestamp of the most recent row addition or removal in
         smartmonDeviceMetadataTable.  Managers may poll this object to detect
         device inventory changes without walking the full table."
    ::= { smartmonCommonObjects 2 }

smartmonDeviceCountNvme OBJECT-TYPE
    SYNTAX      Unsigned32
    MAX-ACCESS  read-only
    STATUS      current
    DESCRIPTION
        "Number of devices in smartmonDeviceMetadataTable whose
         smartmonDeviceType is nvme(5)."
    ::= { smartmonCommonObjects 4 }

smartmonDeviceCountAta OBJECT-TYPE
    SYNTAX      Unsigned32
    MAX-ACCESS  read-only
    STATUS      current
    DESCRIPTION
        "Number of devices in smartmonDeviceMetadataTable whose
         smartmonDeviceType is ata(1) or sat(2)."
    ::= { smartmonCommonObjects 5 }

smartmonDeviceCountSas OBJECT-TYPE
    SYNTAX      Unsigned32
    MAX-ACCESS  read-only
    STATUS      current
    DESCRIPTION
        "Number of devices in smartmonDeviceMetadataTable whose
         smartmonDeviceType is scsi(3) or sas(4)."
    ::= { smartmonCommonObjects 6 }

-- --------------------------------------------------------------------------
-- Device tables
--
-- Split into two tables sharing the same row set (one row per monitored
-- device, keyed by smartmonDeviceIndex): metadata columns that are static
-- identity (name, path, model, serial, ...) live in
-- smartmonDeviceMetadataTable, while columns that change on every poll
-- cycle (poll time/result/exit-status, live power state) live in
-- smartmonDeviceStatusTable.  Splitting them keeps
-- smartmonDeviceTableLastChange meaningful (it tracks row add/remove plus
-- genuine identity changes) instead of firing on every successful poll.
-- --------------------------------------------------------------------------

smartmonDeviceMetadataTable OBJECT-TYPE
    SYNTAX      SEQUENCE OF SmartmonDeviceMetadataEntry
    MAX-ACCESS  not-accessible
    STATUS      current
    DESCRIPTION
        "Central inventory of all storage devices currently monitored by
         the smartctl agent.  One row per device, holding identity columns
         that rarely change.  See smartmonDeviceStatusTable for the
         per-poll columns of the same device set.

         The index smartmonDeviceIndex is a locally assigned table index.
         It is only required to remain unique within smartmonDeviceMetadataTable
         while the agent is running.  Implementations MAY reuse index
         values after agent restart, rediscovery, or configuration changes.
         Managers MUST NOT use smartmonDeviceIndex as persistent device
         identity.

         If the monitored smartctl target can be correlated with an
         ENTITY-MIB physical entity, smartmonDevicePhysicalIndex SHOULD
         contain the corresponding entPhysicalIndex value.  Managers should
         prefer smartmonDevicePhysicalIndex for cross-MIB correlation when
         it is non-zero.

          Managers that need stable disk identity SHOULD join from this index
          to protocol-specific identity columns and derive a persistent key
          from the strongest available hardware identifier, preferring WWN,
          NAA, EUI-64, NGUID, or namespace identifiers where available and
          otherwise using a deterministic normalized model plus serial key.

          Protocol-specific MIBs (SMARTMON-NVME-MIB, SMARTMON-SATA-MIB,
          SMARTMON-SAS-MIB) extend this table by using smartmonDeviceIndex
          as the first component of their own table indices."
    ::= { smartmonCommonObjects 11 }

smartmonPollFailureThreshold OBJECT-TYPE
    SYNTAX      Unsigned32 (1..4294967295)
    MAX-ACCESS  read-only
    STATUS      current
    DESCRIPTION
        "Number of consecutive non-ok smartctl poll results required before
         the agent emits smartmonDevicePollFailed for a device.  Managers can
         display this value alongside poll-failure notifications to explain
         the configured hysteresis."
    ::= { smartmonCommonObjects 7 }

smartmonDeviceUdevTableRowCount OBJECT-TYPE
    SYNTAX      Unsigned32
    MAX-ACCESS  read-only
    STATUS      current
    DESCRIPTION
        "Total number of rows currently in smartmonDeviceUdevTable, summed
         across all devices.  Always 0 when the agent is not running in
         collect mode, since the table is then permanently empty."
    ::= { smartmonCommonObjects 8 }

smartmonDeviceUdevTableLastChange OBJECT-TYPE
    SYNTAX      DateAndTime
    MAX-ACCESS  read-only
    STATUS      current
    DESCRIPTION
        "Timestamp of the most recent change to the contents of
         smartmonDeviceUdevTable.  Always epoch (the agent start time) when
         the agent is not running in collect mode, since the table is then
         permanently empty."
    ::= { smartmonCommonObjects 9 }

smartmonDeviceMetadataEntry OBJECT-TYPE
    SYNTAX      SmartmonDeviceMetadataEntry
    MAX-ACCESS  not-accessible
    STATUS      current
    DESCRIPTION
        "One row in the device inventory.  A row is created when the agent
         first discovers or is configured with a device, and removed when
         the device is no longer monitored.  The matching row in
         smartmonDeviceStatusTable shares the same smartmonDeviceIndex."
    INDEX { smartmonDeviceIndex }
    ::= { smartmonDeviceMetadataTable 1 }

SmartmonDeviceMetadataEntry ::= SEQUENCE {
    smartmonDeviceIndex              Unsigned32,
    smartmonDeviceName                DisplayString,
    smartmonDevicePath                DisplayString,
    smartmonDeviceType                SmartmonDeviceType,
    smartmonDevicePhysicalIndex       PhysicalIndexOrZero,
    smartmonDeviceUris                OCTET STRING,
    smartmonDeviceModelFamily         DisplayString,
    smartmonDeviceModelName           DisplayString,
    smartmonDeviceSerialNumber        DisplayString,
    smartmonDeviceFirmwareVersion     DisplayString,
    smartmonDeviceWwn                 DisplayString
}

smartmonDeviceIndex OBJECT-TYPE
    SYNTAX      Unsigned32 (1..4294967295)
    MAX-ACCESS  not-accessible
    STATUS      current
    DESCRIPTION
        "A locally assigned index for a monitored smartctl target.
         Managers MUST NOT use this value as a persistent device identity.

         The agent derives the initial index as a 32-bit FNV-1a hash of
         the concatenation serial_number|model_name, so the same device
         tends to receive the same value after an agent restart when its
         serial number and model name are unchanged.  This is an
         implementation convenience, not a guarantee; hash collisions or
         device replacements may result in a different index.

         For persistent device identity use smartmonDeviceSerialNumber and
         smartmonDeviceModelName, or smartmonDeviceWwn when available."
    ::= { smartmonDeviceMetadataEntry 1 }

    
smartmonDeviceName OBJECT-TYPE
    SYNTAX      DisplayString
    MAX-ACCESS  read-only
    STATUS      current
    DESCRIPTION
        "Short human-readable device label used in notifications and
         log messages, for example nvme0 or sda.  Typically derived
         from the last component of smartmonDevicePath, but may be
         overridden by agent configuration."
    ::= { smartmonDeviceMetadataEntry 2 }

smartmonDevicePath OBJECT-TYPE
    SYNTAX      DisplayString
    MAX-ACCESS  read-only
    STATUS      current
    DESCRIPTION
        "Device node or smartctl target string passed to smartctl,
         for example /dev/sda or /dev/nvme0.  For RAID pass-through
         targets this may include a controller suffix such as
         /dev/sda -d megaraid,2."
    ::= { smartmonDeviceMetadataEntry 3 }

smartmonDeviceType OBJECT-TYPE
    SYNTAX      SmartmonDeviceType
    MAX-ACCESS  read-only
    STATUS      current
    DESCRIPTION
        "Transport family used to communicate with this device, as
         determined or overridden by smartctl.  The value drives which
         protocol-specific MIB table (NVMe, SATA, SAS) contains data
         for this device index."
    ::= { smartmonDeviceMetadataEntry 4 }

smartmonDevicePhysicalIndex OBJECT-TYPE
    SYNTAX      PhysicalIndexOrZero
    MAX-ACCESS  read-only
    STATUS      current
    DESCRIPTION
        "The entPhysicalIndex value of the ENTITY-MIB physical entity
         associated with this monitored smartctl target.

         A value of zero indicates that the agent could not associate the
         smartctl target with an ENTITY-MIB physical entity.

         When non-zero, this object is intended for cross-MIB correlation
         between SMART monitoring data and ENTITY-MIB inventory data."
    ::= { smartmonDeviceMetadataEntry 5 }

smartmonDeviceUris OBJECT-TYPE
    SYNTAX      OCTET STRING
    MAX-ACCESS  read-only
    STATUS      current
    DESCRIPTION
        "Uniform Resource Identifiers associated with this device.
         Multiple URIs may be present and are separated by white space
         characters.  Leading and trailing white space characters are
         ignored.

         If no URI identification information is known about the device,
         the object is not instantiated.  A zero-length octet string may
         also be returned in this case."
    ::= { smartmonDeviceMetadataEntry 6 }

smartmonDeviceModelFamily OBJECT-TYPE
    SYNTAX      DisplayString
    MAX-ACCESS  read-only
    STATUS      current
    DESCRIPTION
        "Drive model family as identified in the smartctl database
         (model_family).  Present for ATA/SATA devices; empty for NVMe
         and SAS/SCSI devices."
    ::= { smartmonDeviceMetadataEntry 7 }

smartmonDeviceModelName OBJECT-TYPE
    SYNTAX      DisplayString
    MAX-ACCESS  read-only
    STATUS      current
    DESCRIPTION
        "Drive model name as reported by the device (model_name for
         ATA/NVMe; scsi_model_name for SAS/SCSI)."
    ::= { smartmonDeviceMetadataEntry 8 }

smartmonDeviceSerialNumber OBJECT-TYPE
    SYNTAX      DisplayString
    MAX-ACCESS  read-only
    STATUS      current
    DESCRIPTION "Drive serial number as reported by the device (serial_number)."
    ::= { smartmonDeviceMetadataEntry 9 }

smartmonDeviceFirmwareVersion OBJECT-TYPE
    SYNTAX      DisplayString
    MAX-ACCESS  read-only
    STATUS      current
    DESCRIPTION "Firmware version string as reported by the device (firmware_version)."
    ::= { smartmonDeviceMetadataEntry 10 }

smartmonDeviceWwn OBJECT-TYPE
    SYNTAX      DisplayString
    MAX-ACCESS  read-only
    STATUS      current
    DESCRIPTION
        "World Wide Name as a 64-bit hex string with 0x prefix
         (e.g. 0x5000cca2a4c5b3cb), matching the Linux
         /dev/disk/by-id/wwn-0x... symlink format.  Present for ATA/SATA and
         SAS/SCSI devices.  For NVMe devices this is empty unless the agent
         is running in collect mode, in which case it may be populated from
         the ID_WWN property reported by udevadm for the device node."
    ::= { smartmonDeviceMetadataEntry 11 }

-- --------------------------------------------------------------------------
-- Device status table: dynamic per-poll columns, same row set as
-- smartmonDeviceMetadataTable (shares smartmonDeviceIndex).
-- --------------------------------------------------------------------------

smartmonDeviceStatusTable OBJECT-TYPE
    SYNTAX      SEQUENCE OF SmartmonDeviceStatusEntry
    MAX-ACCESS  not-accessible
    STATUS      current
    DESCRIPTION
        "Per-poll status for every device in smartmonDeviceMetadataTable.
         One row per device, updated every poll cycle; see
         smartmonDeviceMetadataTable for the device's static identity
         columns."
    ::= { smartmonCommonObjects 12 }

smartmonDeviceStatusEntry OBJECT-TYPE
    SYNTAX      SmartmonDeviceStatusEntry
    MAX-ACCESS  not-accessible
    STATUS      current
    DESCRIPTION
        "One row of per-poll status, keyed by the same smartmonDeviceIndex
         as the matching smartmonDeviceMetadataTable row.

         smartmonDeviceLastPollResult and smartmonDeviceLastPollExitStatus
         together describe the outcome of the most recent smartctl
         invocation.  A result of ok(1) with exit status 0 indicates a
         fully successful poll.  Non-zero exit status values follow the
         smartctl exit-status bit-mask convention (bit 0 = command-line
         parse error, bit 1 = device open failure, etc.)."
    INDEX { smartmonDeviceIndex }
    ::= { smartmonDeviceStatusTable 1 }

SmartmonDeviceStatusEntry ::= SEQUENCE {
    smartmonDeviceLastPollTime       DateAndTime,
    smartmonDeviceLastPollResult     SmartmonPollResult,
    smartmonDeviceLastPollExitStatus Unsigned32,
    smartmonDevicePowerState         SmartmonDevicePowerState
}

smartmonDeviceLastPollTime OBJECT-TYPE
    SYNTAX      DateAndTime
    MAX-ACCESS  read-only
    STATUS      current
    DESCRIPTION
        "Wall-clock timestamp of the most recent smartctl poll attempt
         for this device, successful or not.  The value is updated even
         when the poll fails, so managers can detect stale data by
         comparing this against the expected polling interval."
    ::= { smartmonDeviceStatusEntry 1 }

smartmonDeviceLastPollResult OBJECT-TYPE
    SYNTAX      SmartmonPollResult
    MAX-ACCESS  read-only
    STATUS      current
    DESCRIPTION
        "Outcome of the most recent smartctl poll, expressed as a
         normalized enumeration.  See SmartmonPollResult in
         SMARTMON-TC-MIB for the full value set.  For detailed
         diagnosis, consult smartmonDeviceLastPollExitStatus."
    ::= { smartmonDeviceStatusEntry 2 }

smartmonDeviceLastPollExitStatus OBJECT-TYPE
    SYNTAX      Unsigned32
    MAX-ACCESS  read-only
    STATUS      current
    DESCRIPTION
        "Raw exit status returned by smartctl for the last poll, encoded
         as a bit mask per the smartctl(8) manual:
           bit 0  -- command-line parse error or invalid usage
           bit 1  -- device open failure
           bit 2  -- SMART or ATA command failed
           bit 3  -- disk failing according to SMART
           bit 4  -- some prefail attributes below threshold
           bit 5  -- some prefail attributes below threshold in the past
           bit 6  -- error log contains records
           bit 7  -- self-test log contains errors
         A value of 0 indicates a fully successful poll."
    ::= { smartmonDeviceStatusEntry 3 }

smartmonDevicePowerState OBJECT-TYPE
    SYNTAX      SmartmonDevicePowerState
    MAX-ACCESS  read-only
    STATUS      current
    DESCRIPTION
        "The device's live power-saving state, as of the agent's last
         poll/probe.  Only probed for ATA/SATA/SCSI/SAS drives in collect
         mode (collect: true / --collect) with respect_standby enabled (the
         default).  In file mode, for NVMe devices, or when standby gating
         is disabled, this reports 'unknown(0)' or 'active(1)' rather than a
         genuine per-tier reading.  See SmartmonDevicePowerState for the
         per-tier semantics."
    ::= { smartmonDeviceStatusEntry 4 }

-- --------------------------------------------------------------------------
-- udevadm property table
-- --------------------------------------------------------------------------

smartmonDeviceUdevTable OBJECT-TYPE
    SYNTAX      SEQUENCE OF SmartmonDeviceUdevEntry
    MAX-ACCESS  not-accessible
    STATUS      current
    DESCRIPTION
        "Generic name/value table of udevadm properties for each monitored
         device, as reported by 'udevadm info --query=property' for the
         device node.  Each row is one property; the same property name may
         legitimately repeat across different devices but not within one
         device's rows.

         This table is populated only when the agent is running in collect
         mode (collect: true / --collect), since udevadm requires a live
         device node.  In file mode this table is always empty.

         Property names and the set of properties present are
         implementation- and kernel/udev-version-dependent; managers SHOULD
         treat smartmonDeviceUdevName as an opaque string rather than
         assuming a fixed schema."
    ::= { smartmonCommonObjects 10 }

smartmonDeviceUdevEntry OBJECT-TYPE
    SYNTAX      SmartmonDeviceUdevEntry
    MAX-ACCESS  not-accessible
    STATUS      current
    DESCRIPTION
        "One udevadm property for one device."
    INDEX { smartmonDeviceIndex, smartmonDeviceUdevRowIndex }
    ::= { smartmonDeviceUdevTable 1 }

SmartmonDeviceUdevEntry ::= SEQUENCE {
    smartmonDeviceUdevRowIndex Unsigned32,
    smartmonDeviceUdevName     DisplayString,
    smartmonDeviceUdevValue    DisplayString
}

smartmonDeviceUdevRowIndex OBJECT-TYPE
    SYNTAX      Unsigned32 (1..4294967295)
    MAX-ACCESS  not-accessible
    STATUS      current
    DESCRIPTION
        "Row ordinal over the udevadm properties collected for this device.
         Carries no meaning beyond row order; not stable across polls if the
         set of properties udevadm reports for the device changes."
    ::= { smartmonDeviceUdevEntry 1 }

smartmonDeviceUdevName OBJECT-TYPE
    SYNTAX      DisplayString
    MAX-ACCESS  read-only
    STATUS      current
    DESCRIPTION
        "The udevadm property key, e.g. ID_WWN, ID_FS_TYPE, DEVLINKS,
         UDISKS_MD_MEMBER_LEVEL."
    ::= { smartmonDeviceUdevEntry 2 }

smartmonDeviceUdevValue OBJECT-TYPE
    SYNTAX      DisplayString
    MAX-ACCESS  read-only
    STATUS      current
    DESCRIPTION
        "The udevadm property value, verbatim as reported by
         'udevadm info --query=property'.  Properties that are themselves
         space-separated lists (e.g. DEVLINKS) are not split; the full
         string is reported as a single value."
    ::= { smartmonDeviceUdevEntry 3 }

-- --------------------------------------------------------------------------
-- Notifications
-- --------------------------------------------------------------------------

smartmonDeviceDiscovered NOTIFICATION-TYPE
    OBJECTS {
        smartmonDeviceName,
        smartmonDevicePath,
        smartmonDeviceType,
        smartmonDeviceLastPollTime,
        smartmonDeviceTableRowCount
    }
    STATUS      current
    DESCRIPTION
        "Generated when a new device row is added to smartmonDeviceMetadataTable,
         for example when a device is hot-plugged or when the agent is
         reconfigured to monitor an additional target.
         smartmonDeviceTableRowCount reflects the updated total after the addition."
    ::= { smartmonCommonNotifications 1 }

smartmonDeviceRemoved NOTIFICATION-TYPE
    OBJECTS {
        smartmonDeviceName,
        smartmonDevicePath,
        smartmonDeviceType,
        smartmonDeviceLastPollTime,
        smartmonDeviceTableRowCount
    }
    STATUS      current
    DESCRIPTION
        "Generated when a device row is removed from smartmonDeviceMetadataTable,
         for example when a device is unplugged or removed from the
         agent's monitored set.
         smartmonDeviceTableRowCount reflects the updated total after the removal."
    ::= { smartmonCommonNotifications 2 }

smartmonDevicePollFailed NOTIFICATION-TYPE
    OBJECTS {
        smartmonDeviceName,
        smartmonDevicePath,
        smartmonDeviceLastPollResult,
        smartmonDeviceLastPollExitStatus,
        smartmonDeviceLastPollTime,
        smartmonPollFailureThreshold
    }
    STATUS      current
    DESCRIPTION
        "Generated when a smartctl poll attempt returns a non-ok result.
         Repeated poll failures may indicate a device or driver problem.
         Implementations SHOULD apply hysteresis to avoid notification
         storms when a device is intermittently unreachable.  The configured
         consecutive-failure threshold is exposed by
         smartmonPollFailureThreshold."
    ::= { smartmonCommonNotifications 3 }

-- --------------------------------------------------------------------------
-- Conformance
-- --------------------------------------------------------------------------

smartmonCommonCompliance MODULE-COMPLIANCE
    STATUS      current
    DESCRIPTION
        "Compliance statement for SMARTMON-COMMON-MIB.  All implementations
         MUST support the device table and device metadata scalars.
         Notification support is optional but RECOMMENDED."
    MODULE
        MANDATORY-GROUPS {
            smartmonDeviceGroup,
            smartmonDeviceScalarGroup
        }
        GROUP smartmonCommonNotificationGroup
        DESCRIPTION
            "Required for implementations that emit device lifecycle
             or poll-failure notifications."
        GROUP smartmonDeviceUdevGroup
        DESCRIPTION
            "Required for implementations that populate
             smartmonDeviceUdevTable.  Not applicable to implementations
             that only ever run in file mode, since the table is then
             permanently empty."
    ::= { smartmonCommonCompliances 1 }

smartmonDeviceScalarGroup OBJECT-GROUP
    OBJECTS {
        smartmonDeviceTableRowCount,
        smartmonDeviceTableLastChange,
        smartmonDeviceCountNvme,
        smartmonDeviceCountAta,
        smartmonDeviceCountSas,
        smartmonPollFailureThreshold
    }
    STATUS current
    DESCRIPTION
        "Scalar objects providing aggregate device inventory information
         including row count, last-change timestamp, and per-type counts."
    ::= { smartmonCommonGroups 1 }

smartmonDeviceGroup OBJECT-GROUP
    OBJECTS {
        smartmonDeviceName,
        smartmonDevicePath,
        smartmonDeviceType,
        smartmonDeviceLastPollTime,
        smartmonDeviceLastPollResult,
        smartmonDeviceLastPollExitStatus,
        smartmonDevicePhysicalIndex,
        smartmonDeviceUris,
        smartmonDeviceModelFamily,
        smartmonDeviceModelName,
        smartmonDeviceSerialNumber,
        smartmonDeviceFirmwareVersion,
        smartmonDeviceWwn,
        smartmonDevicePowerState
    }
    STATUS current
    DESCRIPTION
        "Per-device inventory and poll-status objects from
         smartmonDeviceMetadataTable and smartmonDeviceStatusTable."
    ::= { smartmonCommonGroups 2 }

smartmonDeviceUdevGroup OBJECT-GROUP
    OBJECTS {
        smartmonDeviceUdevTableRowCount,
        smartmonDeviceUdevTableLastChange,
        smartmonDeviceUdevName,
        smartmonDeviceUdevValue
    }
    STATUS current
    DESCRIPTION
        "Generic udevadm name/value objects from smartmonDeviceUdevTable,
         populated only in collect mode."
    ::= { smartmonCommonGroups 4 }

smartmonCommonNotificationGroup NOTIFICATION-GROUP
    NOTIFICATIONS {
        smartmonDeviceDiscovered,
        smartmonDeviceRemoved,
        smartmonDevicePollFailed
    }
    STATUS current
    DESCRIPTION
        "Notifications for device lifecycle events (discovered, removed)
         and poll failures."
    ::= { smartmonCommonGroups 3 }

END
